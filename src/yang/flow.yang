module flow {
  namespace "http://com/example/flow";
  prefix flow;

  import ietf-inet-types {
    prefix inet;
  }
  import tailf-common {
    prefix tailf;
  }
  import tailf-ncs {
    prefix ncs;
  }
  grouping flow_node {
    leaf Device {
      type string;
    }
    leaf Prefix {
      type inet:ipv4-address;
    }
    leaf Netmask {
      type uint32;
    }
  }

  augment /ncs:services {
    list flow {
      description "This is an RFS skeleton service";
      uses ncs:service-data;
      ncs:servicepoint "flow-servicepoint";
      key name;
      leaf name {
        tailf:info "Unique service id";
        tailf:cli-allow-range;
        type string;
      }

      /*
      // may replace this with other ways of refering to the devices.
      leaf-list device {
        type leafref {
          path "/ncs:devices/ncs:device/ncs:name";
        }
      }*/

      container graphImport{
        list graph{
          key "graphName";
          leaf graphName{type string;}
          leaf nodeNum{type uint32;}
          leaf edgeNum{type uint32;}
          list nodeInfo{
            key "deviceID";
            leaf deviceID{type uint32;}
            leaf deviceName{type string;}
          }
          list edge{
            key "souDevice desDevice";
            leaf souDevice{type uint32;}
            leaf desDevice{type uint32;}
          }
        }
      }

      container flowTable{
        list flow{
          key "Description";
          leaf Description{
            type string;
            description "Must to indicate the flow item's detail info include the source&des prefixes";
          }
          
          container source_node{
            uses flow_node;
          }
          container des_node{
            uses flow_node;
          }
          leaf pathType{
            type enumeration{
              enum auto;
              enum manual;
              enum optional;
            }
          }
          leaf-list specificPath{
            type string;
            description "Device list of the whole manual path";
          }
          leaf-list optionalPath{
            type string;
            description "The only devices you point out of the optional path";
          }
        }
      }

    }
  }
}
